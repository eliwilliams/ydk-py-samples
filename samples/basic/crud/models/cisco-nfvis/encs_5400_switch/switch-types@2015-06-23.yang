submodule switch-types {
  belongs-to switch {
    prefix s;
  }

  import tailf-common {
    prefix tailf;
  }

  description
    "Common types used within switch.";

  revision 2015-06-23 {
    description
      "Initial revision.";
  }

  typedef te2-interface-type {
    type string {
      pattern "[1-1]+/[2-2]";
      tailf:info "<1-1>/<2-2>;; Interface Id";
    }
  }

  typedef te-interface-type {
    type string {
      pattern "[1-1]+/[1-4]";
      tailf:info "<1-1>/<1-4>;; Interface Id";
    }
  }

  typedef ge-interface-type {
    type string {
      pattern "[1-1]+/[0-7]";
      tailf:info "<1-1>/<0-7>;; Interface Id";
    }
  }

  typedef iifs-range-type {
    type string {
        //pattern "[1-1]+/[0-7]+-[0-7]+";
        //pattern "1+/[0-7]+-1+/[0-7]+";
        //pattern "[0-7]+-[0-7]+";
        pattern "[0-7]+";
    }
  }

  typedef prefixLengthIPv4 {
    type int32 {
      range "0..32";
    }
  }

  typedef prefixLengthIPv6 {
    type int32 {
      range "0..128";
    }
  }

  typedef interfaceName {
    type string {
      length "1..30";
      pattern "[A-Za-z][^/:.]*";
    }
  }

  typedef interfaceLogicalUnit {
    type int32 {
      range "0..9999";
    }
  }

  typedef vlan-type {
    type uint16 {
      range "1..2349|2450..4093";
      tailf:info "<1-2349>|<2450-4093>;; VLAN number";
    }
  }

  typedef port-channel-type {
    type uint8 {
      range "1..4";
      tailf:info "<1-4>;; Port-channel number";
    }
  }

  // IPv4 prefix (address and mask length) in A.B.C.D/P format
  typedef ipv4-prefix {
    type string {
      pattern
        '(([0-9]|[1-9][0-9]|1[0-9][0-9]|2[0-4][0-9]|25[0-5])\.){3}'
        +  '([0-9]|[1-9][0-9]|1[0-9][0-9]|2[0-4][0-9]|25[0-5])'
        + '/(([0-9])|([1-2][0-9])|(3[0-2]))';
    }
  }

  // IPv6 prefix in standard format
  typedef ipv6-prefix {
    type string {
      pattern '((:|[0-9a-fA-F]{0,4}):)([0-9a-fA-F]{0,4}:){0,5}'
        + '((([0-9a-fA-F]{0,4}:)?(:|[0-9a-fA-F]{0,4}))|'
        + '(((25[0-5]|2[0-4][0-9]|[01]?[0-9]?[0-9])\.){3}'
        + '(25[0-5]|2[0-4][0-9]|[01]?[0-9]?[0-9])))'
        + '(/(([0-9])|([0-9]{2})|(1[0-1][0-9])|(12[0-8])))';
      pattern '(([^:]+:){6}(([^:]+:[^:]+)|(.*\..*)))|'
        + '((([^:]+:)*[^:]+)?::(([^:]+:)*[^:]+)?)'
        + '(/.+)';
    }
  }
}
