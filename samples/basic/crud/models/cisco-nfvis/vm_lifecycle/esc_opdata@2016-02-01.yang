submodule esc_opdata {

  belongs-to vmlc { prefix esc; }

  include esc_opdata_tenant;
  include esc_opdata_devstats;
  include esc_opdata_networks;
  include esc_opdata_images;
  include esc_opdata_flavors;
  include esc_opdata_system_config;

  organization "Cisco Systems";

  contact "Shesha Sreenivasamurthy <shesha@cisco.com>";
  
  revision 2016-02-01 {
    description "Add ESC System configuration details ";
  }
  revision 2015-07-06 {
    description "Add operational data for images and flavors";
  }
  revision 2014-08-06 {
    description "Elastic Services Controller Module's operational data";
  }

  grouping esc_opdata {
    leaf status {
      description "Status of ESC";
      type string;
    }

    /* ESC VM statstics */
    uses esc_opdata_devstats;

    /* ESC system config parameters */
    uses esc_opdata_system_config;

    /* Shared networks created at admin tenant */
    uses esc_opdata_networks;
    
    /* Public images created at admin tenant */
    uses esc_opdata_images;
    
    /* Public flavors created at admin tenant */
    uses esc_opdata_flavors;

    /* Opdata of the VNFs spun by ESC */
    uses esc_opdata_tenant;
  }
}
