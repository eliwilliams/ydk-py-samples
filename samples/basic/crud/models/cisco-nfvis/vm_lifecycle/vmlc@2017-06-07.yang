module vmlc {
  /*
   * This is the top level YANG module. This imports the datamodel
   * module and that include the rest of YANG modules.
   */
  namespace "http://www.cisco.com/nfvis/vm_lifecycle";
  prefix "vmlc";

  import tailf-common { prefix "tailf"; }
   
  include esc_datamodel;
  include esc_opdata;
  include esc_info;
  include esc_types;
  include esc_network;
  include esc_disk;
  include esc_flavor;
  include esc_policies;
  include esc_volume;
  include esc_interface;
  include esc_kpi;
  include esc_rules;
  include esc_config_data;
  include esc_port_forwarding;
  include esc_scaling;
  include esc_extension;
  include esc_property;
  include esc_opdata_interface;
  include esc_opdata_tenant;
  include esc_opdata_devstats;
  include esc_opdata_networks;
  include esc_opdata_images;
  include esc_opdata_flavors;
  include esc_opdata_system_config;  
  include esc_opdata_flavor_state_machine;
  include esc_opdata_image_state_machine;
  include esc_opdata_volumes;
  include esc_opdata_state_machines;

  include "esc_notifications";

  organization "Cisco Systems";

  contact "Shesha Sreenivasamurthy <shesha@cisco.com>";

  description
    "YANG version of the Elastic Service Controller.  This is a complete
     service orchestration module that can dynamically expand and
     reduce your service capacity based on your description of
     LOAD. This module guarantees that the services will be online
     until you tear it down.  This module enables your to: (config it)
     -> (deploy it) -> (forget it)";


  revision 2017-06-07 {
     description "Removed use of imports to simplify version tracking";
  }
  revision 2015-07-23 {
     description "Added support for Tenant Network creation-network directly under tenant";
  }
  revision 2015-07-14 {
    description "Added a new deployment model under tenant";
  }
  revision 2015-06-29 {
    description 
      "ESC Datamodel change to support independent creation of 
       images and flavors";
  }
  revision 2014-06-23 {
    description "Elastic Services Controller Module";
  }

  container vm_lifecycle {

    description
      "Top-level container for all ESC database objects.";
      
    tailf:info "This module contains a collection of YANG definitions related to VM lifecycle management";

    leaf version {
      type escversion;
      config false;
      mandatory true;
      description "ESC version";
    }

    /*
     * This contains services and associated definitions of the VMs
     * for the service.  This information is editable only by admin,
     * but readable by all tenants
     */
    uses svc_datamodel;

    /*
     * This is editable by admin and tenants.
     * Tenant-A will not be able to read or write any configs of Tenant-B
     * Configs specified by the tenants are merged with the ones specified
     * by the admin. The values specified by the admin takes presidence.
     */

    container tenants {
      list tenant {
        key "name";
        description "List of tenants";
        leaf name {
          type escname;
          mandatory true;
        }
        uses esc_network;
        uses tenant_datamodel;
        uses tenant_dep_model;
      }
    }

    /*
     * This represents the external networks that are shared among all
     * the tenants. This is typically created by the admin of the
     * data center typically as part of infrastructure setup.
     * During deployment, the names of the network created here are
     * specified in the interfaces section to associate interfaces
     * wih these networks.
     */
    uses esc_network;
    
    /*
     * This contains the images and its attributes. This is created by
     * the admin or the ESC default tenant. 
     */
    uses esc_images;
    
    /*
     * This contains the flavors and its attributes. This is created by 
     * the admin or the ESC default tenant.
     */
    uses esc_flavors;

    container opdata {
      presence "Indicates that ESC has exported some operational data";
      description
        "This contains all the operational data of the services that have been
         registered and/or instantiated. This is operational data,
         means it is READ-ONLY. Subtrees under this will inherit
         READ-ONLY property, thereby entire subtree becomes READ-ONLY";
      config false;
      tailf:callpoint opdata;
      uses esc_opdata;
    } /* END opdata */

    container info {
      presence "Indicates that ESC has exported its infomation";
      description
        "This contains all the information related to versions and copytights";
      config false;
      tailf:callpoint opdata;
      uses esc_info;
    } /* END info */
  }

  rpc serviceAction {
    description "Service actions including stop, start, reboot, disable-monitor and enable monitor.";
    tailf:actionpoint escrpc;
    input {
      leaf actionType {
        mandatory true;
        description "Service action type";
        type action_types;
      }
      leaf tenantName {
        mandatory true;
        description "Tenant Name";
        type escname;
      }
      leaf depName {
        mandatory true;
        description "Deployment Name";
        type escname;
      }
      leaf serviceName {
        mandatory true;
        description "Service Name";
        type escname;
      }
      leaf serviceVersion {
        mandatory true;
        description "Service Version";
        type escname;
      }
    }
  }

  rpc vmAction {
    description "VM actions including stop, start, reboot, disable-monitor and enable monitor.";
    tailf:actionpoint escrpc;
    input {
      leaf actionType {
        mandatory true;
        description "VM action type";
        type action_types;
      }
      leaf vmName {
        mandatory true;
        description "VM Name";
        type escname;
      }
    }
  }
}
