submodule esc_types {
  /*
   * This file contains custom data types that are used by all other YANG models.
   */
  belongs-to vmlc { prefix esc; }

  import ietf-inet-types { prefix "ietf-inet-types"; }
  import ietf-yang-types { prefix "ietf-yang-types"; }

  organization "Cisco Systems";

  contact "Shesha Sreenivasamurthy <shesha@cisco.com>";

  description
    "ESC's types declarations";
  
  revision 2016-01-22 {
    description "Added a new event type VM_RECOVERY_CANCELLED and VM_RECOVERY_REBOOT";
  }
  revision 2015-11-05 {
    description "Remove EiB support for volumes";
  }
  revision 2015-09-21 {
    description "Added a leaf to config if redeploy is needed after reboot fails upon recovery";
  }
  revision 2015-08-21 {
    description "Removed union types for xpaths";
  }
  revision 2015-07-30 {
    description "Added new enum types in iface_type to support sr-iov";
  }
  revision 2015-07-24 {
    description "Added host_placement and zone_placement to placement_type";
  }
  revision 2015-07-23 {
    description "Added event type VM_UPDATED. Revision header update in data model.";
  }
  revision 2015-07-14 {
    description "Added VIM_OPERATIONAL_STATE and removed ESC_IN_SERVICE and ESC_OUT_OF_SERVICE.";
  }
  revision 2015-06-29 {
    description "ESC Types added for create/delete image/flavor";
  }
  revision 2015-06-08 {
    description "added types escuint8, escuint16, escuint32 for esc_port_forwarding";
  }
  revision 2014-06-23 {
    description "ESC Types";
  }
  
  /****************** ESC DATA TYPES **********************/
  /*
   * Generic esc data type where you can specify xpath or actual value
   */

  typedef escfloat {
    type string;
    reference "http://www.w3.org/TR/xmlschema-2/#float";
  }

  typedef escname {
    type string {
      pattern "[a-zA-Z0-9.\-_]*";
      length 1..256;
    }
  }

  typedef escversion {
    type string { length 1..16; }
  }

  typedef escnetname {
    /*
     * Network name. 1024 is the max length allowed by
     * underlying infrastructure.
     */
    type string { length 1..1024; }
  }

  typedef escbigdata {
    type string { length 1..16384; } /* 16K */
  }

  typedef escipaddr {
    type ietf-inet-types:ip-address;
  }
  typedef escmacaddr {
    type ietf-yang-types:mac-address;
  }
  
  typedef license_key_type {
    type enumeration {
        enum mac_addr;
    }
  }
  
  typedef license_key_value {
	  type string { length 1..256; }
  }

  /****************** EVENT TYPES **********************/
  /*
   * These are the event types that are defined in EDCS: 1312696.
   * This represents the events/callbacks generated by Core-ESC.
   */
  typedef event_types {
    type enumeration {
      enum CREATE_NETWORK;
      enum DELETE_NETWORK;
      enum CREATE_SUBNET;
      enum DELETE_SUBNET;
      enum CREATE_TENANT;
      enum DELETE_TENANT;
      enum CREATE_IMAGE;
      enum DELETE_IMAGE;
      enum CREATE_FLAVOR;
      enum DELETE_FLAVOR;
      enum SERVICE_REGISTRATION;
      enum SERVICE_UNREGISTRATION;
      enum VM_DEPLOYED;
      enum VM_ALIVE;
      enum VM_UPDATED;
      enum VM_UNDEPLOYED;
      enum SERVICE_ALIVE;
      enum SERVICE_UNDEPLOYED;
      enum VM_SCALE_OUT_INIT;
      enum VM_SCALE_OUT_DEPLOYED;
      enum VM_SCALE_OUT_COMPLETE;
      enum VM_SCALE_IN_INIT;
      enum VM_SCALE_IN_COMPLETE;
      enum VM_RECOVERY_INIT;
      enum VM_RECOVERY_DEPLOYED;
      enum VM_RECOVERY_UNDEPLOYED;
      enum VM_RECOVERY_COMPLETE;
      enum SERVICE_UPDATED;
      enum VM_STOPPED;
      enum SERVICE_STOPPED;
      enum VM_STARTED;
      enum SERVICE_STARTED;
      enum VM_REBOOTED;
      enum SERVICE_REBOOTED;
      enum VM_MONITOR_UNSET;
      enum SERVICE_MONITOR_UNSET;
      enum VM_MONITOR_SET;
      enum VIM_OPERATIONAL_STATE;
      enum VM_RECOVERY_CANCELLED;
      enum VM_RECOVERY_REBOOT;
    }
  }

  /****************** STATUS **********************/
  /*
   * These represent status of the operation requested that
   * are notified to northbound client.
   */

  typedef status {
    type enumeration {
      enum SUCCESS;
      enum FAILURE;
    }
  }

  /****************** SIZE UNITS  **********************/
  /*
   * This is derived from the generic sizeunit_group defined below.
   * Standard size units.
   */
  typedef szunits {
    description "Some standard size units: MiB, GiB, TiB and PiB
                        MiB: 1024^2 (Mebibyte)
                        GiB: 1024^3 (Gibibyte)
                        TiB: 1024^4 (Tebibyte)
                        PiB: 1024^5 (Pebibyte)";
    type enumeration {
      enum MiB;
      enum GiB;
      enum TiB;
      enum PiB;      
    } 
  }

  /****************** IOBUS TYPE  **********************/
  /*
   * Standard IO bus used to attach root/OS disk and secondary volume.
   */
  typedef iobus {
    description "PCI bus interface that is to be used while attaching the OS
                 disk to the domain. Currently supported bus types are IDE,
                 SCSI and VIRTIO";
      type enumeration {
        enum ide;
        enum scsi;
        enum virtio;
      }
  }

  /****************** INTERFACE TYPE  **********************/
  typedef iface_type {
    description "Interface Type: VIRTUAL/PASSTHRU";
    type enumeration {
      enum virtual;
      enum passthru;
      enum direct;
      enum macvtap;
    }
  }

  /****************** VIRTUAL INTERFACE MODEL  **********************/
  /*
   * Types of virtual interface models
   */
  typedef iface_model {
    description
      "Virtual Interface Type: virtio, e1000 etc. Later when we support
       'passthru' interface type we can change this to a union";
    type enumeration {
      enum e1000;
      enum ne2k_pci;
      enum virtio;
      enum i82551;
      enum i82557b;
      enum i82559er;
      enum rtl8139;
      enum pcnet;
    }
  }

  /****************** IP VERSIONS **********************/
  typedef ipversion_t {
    description "ipv4 or ipv6";
    type enumeration {
      enum ipv4;
      enum ipv6;
    } 
  }

  /****************** DISK FORMATS **********************/
  /*
   * Rather than specifying disk formats as a string where user may
   * get confused with what to specify, here having it like an enumeration
   * that enables the user to know what are the different options that are
   * available for him/her.
   */
  typedef disk_formats {
    description "The format of the disk that is being specified as disk source.
                 Currently QCOW2, RAW and VMDK formats are supported.";
    type enumeration {
      enum qcow2;
      enum raw;
      enum vmdk;
    }
  }


  /*******************   METRIC CONDITIONS *****************/
  typedef conditions {
    description
      "Different conditions supported with respect to metric comparison";
    type enumeration {
      enum GT;
      enum LT;
      enum EQ;
      enum GE;
      enum LE;
    }
  }

  /*********************   METRIC TYPES ********************/
  typedef metric_types {
    description
      "Different conditions supported with respect to metric comparison";
    type enumeration {
      enum INT8;
      enum INT16;
      enum INT32;
      enum UINT8;
      enum UINT16;
      enum UINT32;
      enum FLOAT;
      enum DOUBLE;
      enum STRING;
    }
  }

  /*******************  METRIC POLLING UNITS *****************/
  typedef pollunits {
    description "Polling units, seconds or minutes";
    type enumeration {
      enum minutes;
      enum seconds;
    }
  }

  /************ WATCH DOG HARDWARE ************/
  typedef wd_hardware {
    description "Only certain Watchdog hardware are supported current.";
    type enumeration {
      enum i6300esb;
      enum ib700;
    }
  }

  /************ WATCH DOG ACTION ************/
  typedef wd_action {
    description
      "Action that should be taken by the hypervisor when watchdog
       is triggered";
    type enumeration {
      enum reset;
      enum poweroff;
      enum shutdown;
      enum pasue;
      enum debug;
      enum none;
    }
  }

  /************ PLACEMENT AFFINITY TYPES ************/
  typedef placement_type {
    description
      "Whether VMs of two groups to be place together (affinity) or on separate
       hosts (anti_affinity), also whether VMs should be placed on a host or in a zone";
    type enumeration {
      enum affinity;
      enum anti_affinity;
      enum zone_host;
    }
  }

  /************ PLACEMENT ENFORCEMENT TYPES ************/
  typedef enforcement {
    description
      "Whether the affinity policy should be strictly or loosely enforced";
    type enumeration {
      enum strict;
      /* CSCus83505comment out loose since it is not supported at this time - when availability zone/aggregates
          are properly supported, loose should be returned as a valid option, so comment out rather than remove
      enum loose;
      */
    }
  }

  /****** IMAGE STATE MACHINE STATES *********/
  typedef image_state_machine_states {
    description "VM state machines states";
    type enumeration {
      enum IMAGE_UNDEF_STATE;
      enum IMAGE_CREATING_STATE;
      enum IMAGE_ACTIVE_STATE;
      enum IMAGE_DELETING_STATE;
      enum IMAGE_DELETED_STATE;
      enum IMAGE_ERROR_STATE;
    }
  }
  
  /****** FLAVOR STATE MACHINE STATES *********/
  typedef flavor_state_machine_states {
    description "VM state machines states";
    type enumeration {
      enum FLAVOR_UNDEF_STATE;
      enum FLAVOR_CREATING_STATE;
      enum FLAVOR_ACTIVE_STATE;
      enum FLAVOR_DELETING_STATE;
      enum FLAVOR_DELETED_STATE;
      enum FLAVOR_ERROR_STATE;
    }
  }
  
  /****** SERVICE STATE MACHINE STATES *********/
  typedef service_state_machine_states {
    description "Service state machines states";
    type enumeration {
      enum SERVICE_UNDEF_STATE;
      enum SERVICE_DEPLOYING_STATE;
      enum SERVICE_INERT_STATE;
      enum SERVICE_ACTIVE_STATE;
      enum SERVICE_UNDEPLOYING_STATE;
      enum SERVICE_STOPPING_STATE;
      enum SERVICE_STOPPED_STATE;
      enum SERVICE_STARTING_STATE;
      enum SERVICE_REBOOTING_STATE;
      enum SERVICE_ERROR_STATE;
    }
  }

  /****** VM STATE MACHINE STATES *********/
  typedef vm_state_machine_states {
    description "VM state machines states";
    type enumeration {
      enum VM_UNDEF_STATE;
      enum VM_DEPLOYING_STATE;
      enum VM_MONITOR_UNSET_STATE;
      enum VM_MONITOR_DISABLED_STATE;
      enum VM_STOPPING_STATE;
      enum VM_SHUTOFF_STATE;
      enum VM_STARTING_STATE;
      enum VM_REBOOTING_STATE;
      enum VM_INERT_STATE;
      enum VM_ALIVE_STATE;
      enum VM_UNDEPLOYING_STATE;
      enum VM_ERROR_STATE;
    }
  }

    /****** VM GROUP PROPERTIES *********/
  typedef vm_group_properties {
    description "vm_group_properties";
    type enumeration {
      enum NOTIFY_EXTERNAL_MONITOR;
    }
  }

  /****** SERVICE/VM OPERATION TYPES *********/
  typedef action_types {
    description "Service/VM action types";
    type enumeration {
      enum STOP;
      enum START;
      enum REBOOT;
      enum DISABLE_MONITOR;
      enum ENABLE_MONITOR;
    }
  }

  /****** RECOVERY ACTION TYPES *********/
  typedef recovery_action_types {
    description "Recovery action types";
    type enumeration {
      enum REBOOT_THEN_REDEPLOY;
      enum REBOOT_ONLY;
      enum REDEPLOY_ONLY;
    }
  }
}
