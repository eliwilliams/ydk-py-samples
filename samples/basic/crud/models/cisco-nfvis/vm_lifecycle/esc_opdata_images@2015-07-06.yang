submodule esc_opdata_images {

  /*
   * This represents operational data of the images
   */

  belongs-to vmlc { prefix esc; }

  import ietf-yang-types { prefix "ietf-yang-types"; }
  include esc_opdata_image_state_machine;
  
  organization "Cisco Systems";

  contact "Natasha Shrestha <nashrest@cisco.com>";

  revision 2015-07-06 {
    description
      "Elastic Services Controller Module's images' operational data";
  }

  grouping esc_opdata_images {
    description
      "This contains all the operational data of the images";
    container images {
      list image {
        description "Image running information";
        key "name";
        leaf name {
          description "Name of the image";
          type string;
        }
        leaf image_id {
          description "ID of the image";
          type ietf-yang-types:uuid;
        }
        leaf public {
          description "True if the image is public";
          type boolean;
          default true;
        }
        /* State Machine for Image */
        uses esc_opdata_image_state_machine;
      }
    }
  }
}
