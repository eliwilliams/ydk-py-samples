submodule esc_info {

    belongs-to vmlc { prefix esc; }

    organization "Cisco Systems";

    contact "Steve Zhu <hezh@cisco.com>";

    revision 2015-06-05 {
      description "Added info container";
    }
    revision 2014-08-06 {
      description "Elastic Services Controller Module's operational data";
    }

    grouping esc_info {
      leaf product_name {
        description "Official name of ESC";
        type string;
        default "Elastic Services Controller";
      }
      container esc_version {
        description "Version of current ESC load";
        leaf major {
          description "Major version";
          type string;
          default "Unknown";
        }
        leaf minor {
          description "Minor version";
          type string;
          default "Unknown";
        }
        leaf sprint {
          description "Sprint number";
          type string;
          default "Unknown";
        }
        leaf release {
          description "Build number";
          type string;
          default "Unknown";
        }
        leaf yang_model {
          description "Version of YANG data model";
          type string;
          default "Unknown";
        }
        leaf timestamp {
          description "Build timestamp";
          type string;
          default "Unknown";
        }
      }

      container copyright {
        description "ESC copyright info";
        leaf company {
          description "Company who owns ESC";
          type string;
          default "Cisco Systems";
        }
        leaf homepage {
          description "ESC homepage";
          type string;
          default "http://www.cisco.com/c/en/us/support/cloud-systems-management/elastic-services-controller-esc/tsd-products-support-series-home.html";
        }
      }
    }
  }
