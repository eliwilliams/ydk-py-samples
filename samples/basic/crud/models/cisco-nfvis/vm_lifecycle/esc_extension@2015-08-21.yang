submodule esc_extension {

  belongs-to vmlc { prefix esc; }
  
  include esc_property;

  organization "Cisco Systems";

  contact "Elie El Ajaltouni <eelajalt@cisco.com>";

  revision 2015-08-21 {
    description "Add containers within an extension";
  }

  grouping container_list_definition {
    container containers {
      description "List of containers";
      list container {
        key "name";
        leaf name {
          description "Name of container";
          type string;
        }
        uses property_list_definition;
      }
    }     
  }
 
  grouping extension_list_definition{
    container extensions {
      description "List of extensions";
       list extension{
        key "name";
        leaf name {
          description "Name of extension";
          type string;
        }
        uses property_list_definition;
        uses container_list_definition;
      }
    }
  }  
}
