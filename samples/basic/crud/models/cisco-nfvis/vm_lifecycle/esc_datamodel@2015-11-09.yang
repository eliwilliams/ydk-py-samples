submodule esc_datamodel {

  belongs-to vmlc { prefix esc; }

  /*
   * include all the components of the datamodel
   */
  include esc_types;
  include esc_policies;
  include esc_volume;
  include esc_interface;
  include esc_kpi;
  include esc_rules;
  include esc_config_data;
  include esc_port_forwarding;
  include esc_scaling;
  include esc_extension;
  include esc_network;
  include esc_disk;
  include esc_flavor;

  organization "Cisco Systems";
  
  contact "Shesha Sreenivasamurthy <shesha@cisco.com>";
 
  revision 2015-11-09 {
    description "Added a leaf to support volume that was precreated in VIM";
  } 
  revision 2015-09-21 {
    description "Added a leaf to config if redeploy is needed after reboot fails upon recovery";
  }
  revision 2015-07-14 {
    description "Added a new deployment model under tenant";
  }
  revision 2015-06-17 {
    description "ESC Datamodel change to add image and flavor that was precreated in vim";
  }
  revision 2015-06-08 {
    description "added esc_port_forwarding";
  }
  revision 2015-06-04 {
    description "updated description";
  }
  revision 2014-06-23 {
    description "ESC Datamodel";
  }

  grouping misc_params {
    container misc {
      description "Some miscelaneous configurations.";
      container watchdog {
        description "Watch Dog";
        leaf hardware {
          description "Watchdog device to be used. i6300esb or ib700";
          type wd_hardware;
        }

        leaf action {
          description "Action when watchdog fires:
                       reset|shutdown|poweroff|pause|debug|none";
          type wd_action;
        }
      }
    }
  }

  grouping datamodel {

    uses esc_policies;
    uses esc_network;

    list vm_group {
      description
        "This section allows one to define propoerties such as number of interfaces, type of
         monitoring, monitoring frequency, type of eventing, scaling
         mechanism, elasiticiy properties, etc for each VM in this
         group. This represnts a type of VM.  For example, if one
         needs two Webservers in a deployment, only one VM instance is
         defined and number of instances is set to 2 in the scaling
         section. If there are two types of VMs, for example a
         Webserver and a Database server, then such a service will
         have two vm_groups: one for Webserver and another for
         Database server";
      key "name";
      min-elements 1;
      leaf name {
        description "A name for the VM group";
        type escname;
        mandatory true;
      }
      leaf image {
        description  "Image refers to pre-existing image in VIM";
        type escname;
      }
      leaf flavor {
        description  "Flavor refers to pre-existing flavor in VIM";
        type escname;
      }
      leaf volume {
        description  "Volume refers to pre-existing volume in VIM";
        type escname;
      }
      leaf bootup_time {
        description
          "Time in seconds that this VM takes to perform a cold boot. This will
           be the time that ESC waits before deciding that the VM is
           un-bootable.";
        type int32;
        mandatory true;        
      }
      leaf recovery_wait_time {
        description
          "Time in seconds that this VM takes to perform a normal warm
           reboot. This will be used to avoid premature VM recovery in
           case VM becomes unresponsive due to operator reboot. This
           is important as VM recovery will results in loss of data
           that is stored on root disk. If speedy recovery is more
           important than the data on the root disk, this value can be
           optionally set to 0.";
        type int32;
        default 0;        
      }
      
      uses misc_params;
      uses esc_volume_deployment;
      uses esc_interface;
      uses esc_kpi;
      uses esc_rules;
      uses esc_config_data;
      uses esc_port_forwarding;
      uses esc_scaling;
      uses intra_vm_group_placement;
      uses intra_vm_group_properties;
      uses recovery_policies;
      uses extension_list_definition;
    }
  }

  grouping svc_datamodel {
    container services {
      list service_definition {
        key "name version";
        description "List of services";
        leaf name {
          description "Name of the service";
          type escname;
          mandatory true;
        }
        leaf version {
          description "Version of the service";
          type escversion;
          mandatory true;
        }
        list vm_group {
          description
          "This section allows one to define properties such as disk, number of
          CPUs, amount of memory";
          key "name";
          min-elements 1;
          leaf name {            
            description "A name for the VM group";
            type escname;
            mandatory true;
          }
          uses esc_disk;
          uses esc_flavor;
        }
      }
    }
  }

  grouping tenant_datamodel {
    container services {
      list service_definition {
        key "deployment_name name version";
        description "List of services requested by the user";
        leaf deployment_name {
          description
            "User specified name. One can have multiple deployments of the
             same service, but have to provide a unique name for each
             deployment";
          type escname;
          mandatory true;
        }
        leaf name {
          description "Name of the service";
          type escname;
          mandatory true;
        }
        leaf version {
          description "Version of the service";
          type escversion;
          mandatory true;
        }
        uses datamodel;
      }
    }
  }
  
  grouping tenant_dep_model {
    container deployments {
      list deployment {
        key "name";
        description "List of deployments requested by the user";
        leaf name {
          description
            "User specified name. One can have multiple deployments with a unique name for each
             deployment";
          type escname;
          mandatory true;
        }
        
        uses datamodel;
      }
    }
  }
}
