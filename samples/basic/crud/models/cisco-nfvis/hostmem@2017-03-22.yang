submodule hostmem {
    
    belongs-to system_monitoring {
    prefix "system_monitoring";
    }

    import tailf-common { prefix tailf; }

    import ietf-yang-types { prefix yang; }

    import utilization_common {prefix "utilization_common"; }

    organization "Cisco Systems, Inc.";

    description "Host memory details for NFVIS";

    contact "nfvis-yang-models@cisco.com";

    revision 2017-03-22 {
        description
            "Released as part of NFVIS 3.5.1.

             Initial revision";
    }

    grouping systemmemory {
        container memory {
            config false;
            
            container stats {
                tailf:callpoint hostmem;
                config false;

                list mem-usage {
                    uses utilization_common:request_time_info;
                    uses utilization_common:collect_time_info;
                    uses utilization_common:mem_utilization;

                    key "duration";
                    max-elements 1;
                }
            }
        

            container table {
                config false;
                tailf:callpoint hostmem_table;

                list mem-usage {
                    uses utilization_common:request_time_info;

                    key "duration";
                    max-elements 1;

                    list memory {
                        leaf type {
                            type string;
                        }
                        leaf min {
                            type string;
                        }
                        leaf max {
                            type string;
                        }
                        leaf average {
                            type string;
                        }
                    }
                }
            }
        }
    }
}
